(defun bse-plan-length (d / pts q prev total first closed)
 (setq pts nil total 0.0)
 (foreach q d (if (= (car q) 10) (setq pts (append pts (list (cdr q))))))
 (if pts (progn (setq first (car pts) prev first)
 (foreach q (cdr pts) (setq total (+ total (distance prev q)) prev q))
 (if (= 1 (logand 1 (cdr (assoc 70 d)))) (setq total (+ total (distance prev first)))))) total)
(setq auditfile (open "@@OUTPUT@@" "w"))
(write-line (strcat "DRAWING\t" (getvar "DWGPREFIX") (getvar "DWGNAME")) auditfile)
(write-line (strcat "VERSION\t" (getvar "ACADVER")) auditfile)
(write-line (strcat "UNITS\t" (itoa (getvar "INSUNITS"))) auditfile)
(foreach pair (dictsearch (namedobjdict) "ACAD_LAYOUT") (if (= (car pair) 3) (write-line (strcat "LAYOUT\t" (cdr pair)) auditfile)))
(foreach h '(
@@HANDLES@@)
 (setq en (handent h))
 (if en (progn
  (setq d (entget en) ty (cdr (assoc 0 d)) txt "" len "")
  (if (member ty '("TEXT" "MTEXT"))
   (foreach a d (if (member (car a) '(1 3)) (setq txt (strcat txt (cdr a))))))
  (if (= ty "LWPOLYLINE") (setq len (rtos (bse-plan-length d) 2 8)))
  (write-line (strcat h "\t" ty "\t" (cdr (assoc 8 d)) "\t" txt "\t" len "\t" (if (= ty "INSERT") (cdr (assoc 2 d)) "")) auditfile))
  (write-line (strcat h "\tMISSING") auditfile)))
(close auditfile)
(princ "BSE_NATIVE_READ_COMPLETE")
(princ)
